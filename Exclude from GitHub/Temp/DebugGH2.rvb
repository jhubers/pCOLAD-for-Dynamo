Option Explicit

Call DebugGHFile()
Sub DebugGHFile()
  Dim GH
  Set GH = Rhino.GetPluginObject("Grasshopper")
  Call GH.DisableBanner()
  Call GH.ShowEditor()
  Call GH.OpenDocument("D:\Temp\testSpiral1.gh")
  Set GH = Nothing
End Sub
